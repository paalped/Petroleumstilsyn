FME workspace ConvertModel.fmw

Parameters:
- SourceDataset_FILEGDB = C:\Users\paalp\OneDrive - Geodata\Prosjekter\MD-darwin\BarentsVisual\VisuelleDataNCS_MasterDB.gdb   # File Geodatabase
- FEATURE_TYPES_2 = SURVEY_INFO   # Feature Types to Read From gdb
- DestDataset_GEODATABASE_FILE = \\osl-int-md-03\PROSJEKTER\Petroleumstilsyn\petroleumstilsyn4.gdb   # File Geodatabase
- DestDataset_XLSXW_3 = $(FME_MF_DIR)location_species.xlsx   # Destination Microsoft Excel File
- DestDataset_GEODATABASE_FILE_3 = \\osl-int-md-03\PROSJEKTER\Petroleumstilsyn\petroleumstilsyn3.gdb   # File Geodatabase
- DestDataset_POSTGIS = Petroleumsvirksomhet   # Connection

Readers:
- FILEGDB_1: FILEGDB from $(SourceDataset_FILEGDB)

Writers:
- GEODATABASE_FILE_1: GEODATABASE_FILE to $(DestDataset_GEODATABASE_FILE) in EPSG:4326
- XLSXW_1: XLSXW to $(DestDataset_XLSXW_3)
- GEODATABASE_FILE_2: GEODATABASE_FILE to $(DestDataset_GEODATABASE_FILE_3)
- POSTGIS_1: POSTGIS to $(DestDataset_POSTGIS)

Bookmark: LifeCatalogueAPI
SpeciesList_BarentsSea (reader FILEGDB_1)
    attributes: OBJECTID objectid, Taxa text(255), Phylum text(255), Family text(255), AphiaID double, Alke_Nor double, Alke_Sor double, Alta double, Apollo_Apprasial text(255), Apollo_Main text(255), Arenaria text(255), Askeladd_Beta text(255), Askepott double, Atlantis_B text(255), Aurelia double, Bigorna double, Bone double, Byrkje_C text(255), Byrkje_W text(255), Borselv text(255), Caurus double, Darwin_Veslemoy double, Drivis text(255), Eik double, Gamma double, Geres double, Gloppen_1 text(255), Gloppen_2 double, Goliat_Exploration double, Goliat_Eye_alt1 text(255),
      Goliat_Eye_alt2 text(255), Goliat double, Gotha double, Havis double, Isfjell text(255), Iskrystall text(255), Juksa text(255), Jupiter text(255), Kramsno double, Lakselv_South text(255), Lavvo double, Lavvo_Komag double, Mercury text(255), Neiden double, Noaiden text(255), Nordvarg text(255), Pingvin text(255), PL605_North text(255), PL611_Kvalross double, PL605_South double, Rein text(255), Saturn text(255), Skalle double, Skalle_N text(255), Skrugard_Apprasial double, Snohvit_F double, Snohvit06 text(255), Snohvit double, Snohvit_G double, Sorpe text(255),
      Tornerose text(255), Ursus_Major double, Ververis double, Wisting_Alternative text(255), Wisting_Central text(255), Ornen_Nord text(255), Ornen_Sor text(255)
    -> AttributeRemover_2
AttributeRemover_2
    REMOVE_ATTRS = AphiaID,Family,OBJECTID,Phylum
    -> PythonCaller_3
Note: Here we convert the matrix into a list of location containing a list of species. The script is based on hardcoded attribute Taxa, every other field is converted to a location
PythonCaller_3
    NEW_ATTRIBUTES = _location{} location_sightings fme_feature_type _location{}.species{}
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              self.location_sightings = {}
          def input(self,feature):
              for atn in feature.getAllAttributeNames():
                  value = feature.getAttribute(atn)
                  try:
                      if int(value) > 0:
                          if atn not in self.location_sightings.keys():
                              self.location_sightings[atn] = {feature.getAttribute('Taxa'): str(int(value))}
                          elif feature.getAttribute('Taxa') not in self.location_sightings[atn].keys():
                              self.location_sightings[atn][feature.getAttribute('Taxa')] = str(int(value))


                  except Exception:
                      pass
              self.pyoutput(feature)
          def close(self):
              newFeature = fmeobjects.FMEFeature()
              newFeature.setAttribute('location_sightings', str(self.location_sightings))
              newFeature.setAttribute('fme_feature_type', 'location_type')

              for j, (location, species_value) in enumerate(self.location_sightings.items()):
                  newFeature.setAttribute(f'_location{{{j}}}.location', location.replace('_', ' '))
                  for i, (species, sightings) in enumerate(species_value.items()):
                      newFeature.setAttribute(f'_location{{{j}}}.species{{{i}}}.name', species)
                      newFeature.setAttribute(f'_location{{{j}}}.species{{{i}}}.sigthings', sightings)
              self.pyoutput(newFeature)
    PYTHONSYMBOL = FeatureProcessor
    -> FeatureTypeFilter_3
FeatureTypeFilter_3
    ATTRIBUTES = <Blank>,<Unfiltered>,location_type
    <BLANK> -> AttributeManager_9
    <UNFILTERED> -> AttributeManager_9
    location_type -> AttributeKeeper_9
AttributeManager_9
    ATTR_TABLE:
      SET_TO Taxa = @Trim(@Value(Taxa))
      REMOVE Alke_Nor
      REMOVE Alke_Sor
      REMOVE Alta
      REMOVE Apollo_Apprasial
      REMOVE Apollo_Main
      REMOVE Arenaria
      REMOVE Askeladd_Beta
      REMOVE Askepott
      REMOVE Atlantis_B
      REMOVE Aurelia
      REMOVE Bigorna
      REMOVE Bone
      REMOVE Byrkje_C
      REMOVE Byrkje_W
      REMOVE Borselv
      REMOVE Caurus
      REMOVE Darwin_Veslemoy
      REMOVE Drivis
      REMOVE Eik
      REMOVE Gamma
      REMOVE Geres
      REMOVE Gloppen_1
      REMOVE Gloppen_2
      REMOVE Goliat_Exploration
      REMOVE Goliat_Eye_alt1
      REMOVE Goliat_Eye_alt2
      REMOVE Goliat
      REMOVE Gotha
      REMOVE Havis
      REMOVE Isfjell
      REMOVE Iskrystall
      REMOVE Juksa
      REMOVE Jupiter
      REMOVE Kramsno
      REMOVE Lakselv_South
      REMOVE Lavvo
      REMOVE Lavvo_Komag
      REMOVE Mercury
      REMOVE Neiden
      REMOVE Noaiden
      REMOVE Nordvarg
      REMOVE Pingvin
      REMOVE PL605_North
      REMOVE PL611_Kvalross
      REMOVE PL605_South
      REMOVE Rein
      REMOVE Saturn
      REMOVE Skalle
      REMOVE Skalle_N
      REMOVE Skrugard_Apprasial
      REMOVE Snohvit_F
      REMOVE Snohvit06
      REMOVE Snohvit
      REMOVE Snohvit_G
      REMOVE Sorpe
      REMOVE Tornerose
      REMOVE Ursus_Major
      REMOVE Ververis
      REMOVE Wisting_Alternative
      REMOVE Wisting_Central
      REMOVE Ornen_Nord
      REMOVE Ornen_Sor
      SET_TO search_url = http://webservice.catalogueoflife.org/col/webservice?name=
      SET_TO base_url = http://webservice.catalogueoflife.org/col/webservice?
      SET_TO id_url = http://webservice.catalogueoflife.org/col/webservice?id=
      SET_TO genus_search_word = @Value(Taxa)
    -> StringReplacer
StringReplacer
    CASE = NO
    FIND_TEXT = " "
    NO_MATCH = _FME_NO_OP_
    REGEXP = NO
    REPLACE_TEXT = +
    SRC_ATTRS = genus_search_word
    -> HTTPCaller
HTTPCaller
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = @Value(search_url)@Value(Taxa)
    TRANSFER_TIMEOUT_LENGTH = 90
    USE_COOKIES = No
    VERIFY_SSL_CERTIFICATES = Yes
    -> XMLFlattener
XMLFlattener
    ATTRIBUTE_XML = _response_body
    EMBEDDED_EXPRESSIONS = id
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    NEW_ATTRIBUTES = id
    SUB_FRAGMENT_OPTIONS = id
    XML_SOURCE_TYPE = Attribute with XML document
    -> HTTPCaller_2
    <REJECTED> -> AttributeManager_11
AttributeManager_11
    ATTR_TABLE:
      REMOVE search_url
      REMOVE base_url
      REMOVE id_url
      REMOVE genus_search_word
      REMOVE _response_body
      REMOVE _http_status_code
      REMOVE fme_rejection_code
      REMOVE id
    -> BulkAttributeRenamer_27
HTTPCaller_2
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_id
    TARGET_ATTR_ENCODING = auto-detect
    TARGET_URL = @Value(id_url)@Value(id)&format=json&response=full
    TRANSFER_TIMEOUT_LENGTH = 90
    USE_COOKIES = No
    VERIFY_SSL_CERTIFICATES = Yes
    -> JSONFlattener
JSONFlattener
    ERROR_LIST_ATTR = _json_error
    JSON_DOCUMENT = @Value(_response_id)
    NEW_ATTRIBUTES = results{}.classification{}.name results{}.common_names{}.language results{}.common_names{}.name
    READ_FROM_FILE = NO
    RECURSIVE = Yes
    -> PythonCaller
PythonCaller
    NEW_ATTRIBUTES = name_norwegian
    PYTHONSOURCE:
      import fme
      import fmeobjects

      class FeatureProcessor(object):
          def __init__(self):
              pass
          def input(self,feature):
              language_list = feature.getAttribute('results{0}.common_names{}.language')
              try:
                  for i, language in enumerate(language_list):
                      if language.lower() == 'norwegian' or language.lower() == 'norsk':
                          feature.setAttribute('name_norwegian', feature.getAttribute(f'results{{0}}.common_names{{{i}}}.name'))
              except TypeError:
                  pass
              self.pyoutput(feature)
          def close(self):
              pass
    PYTHONSYMBOL = FeatureProcessor
    -> AttributeManager_10
AttributeManager_10
    ATTR_TABLE:
      REMOVE genus_search_word
      REMOVE search_url
      REMOVE base_url
      REMOVE id_url
      REMOVE _response_body
      REMOVE _http_status_code
      REMOVE id
      REMOVE _response_id
      SET_TO Kingdom = @Value(results{0}.classification{0}.name)
      SET_TO Phylum = @Value(results{0}.classification{1}.name)
      SET_TO Class = @Value(results{0}.classification{2}.name)
      SET_TO Order = @Value(results{0}.classification{3}.name)
      SET_TO Family = @Value(results{0}.classification{4}.name)
      SET_TO Genus = @Value(results{0}.classification{5}.name)
      REMOVE _location{}
    -> BulkAttributeRenamer_27
BulkAttributeRenamer_27
    ATTRCHOICE = All Attributes
    CASE_CHANGE_TYPE = lower
    MODE_CHOICE = RENAME
    PATTERN_ACTION_DISP = CASECHANGE
    -> Counter_3
Counter_3
    CNT_ATTR = id
    DOMAIN = counter
    SCOPE = Local
    START = 0
    -> FeatureMerger_3 [SUPPLIER]
AttributeKeeper_9
    KEEP_ATTRS = location_sightings
    KEEP_LIST = _location{}
    -> ListExploder_2
ListExploder_2
    ATTR_ACCUM_MODE = Merge List Attributes
    ATTR_CONFLICT_RES = Use List Attribute Values
    INDEX_ATTR = _element_index
    LIST_ATTR = _location{}
    ELEMENTS -> ListExploder_3
ListExploder_3
    ATTR_ACCUM_MODE = Merge List Attributes
    ATTR_CONFLICT_RES = Use List Attribute Values
    INDEX_ATTR = _element_index2
    LIST_ATTR = species{}
    ELEMENTS -> AttributeExposer
AttributeExposer
    ATTR_LIST = location,name,sigthings
    -> AttributeKeeper_10
AttributeKeeper_10
    KEEP_ATTRS = sigthings,name,location
    -> FeatureMerger_3 [REQUESTOR]
    -> DuplicateFilter_2 [off]
FeatureMerger_3
    ATTR_ACCUM_MODE = Merge Supplier
    ATTR_CONFLICT_RES = Use Requestor
    IGNORE_NULLS = No
    JOIN_KEYS = @Value(name) @Value(taxa) AUTO
    MERGE_TYPE = Attributes Only
    PROCESS_DUPS = NO
    REJECT_NULL_MISSING_KEYS = No
    SUPPLIERS_FIRST = No
    MERGED -> species (writer GEODATABASE_FILE_1)
    MERGED -> species (writer POSTGIS_1)
    UNMERGED_REQUESTOR -> species (writer GEODATABASE_FILE_1)
    UNMERGED_REQUESTOR -> species (writer POSTGIS_1)
species (writer POSTGIS_1)
    attributes: location varchar(200), name varchar(200), sigthings varchar(200), taxa varchar(200), kingdom varchar(200), phylum varchar(200), class varchar(200), order varchar(200), family varchar(200), genus varchar(200), name_norwegian varchar(200), id varchar(200)
species (writer GEODATABASE_FILE_1)
    attributes: location char(200), name char(200), sigthings char(200), taxa char(200), kingdom char(200), phylum char(200), class char(200), order char(200), family char(200), genus char(200), name_norwegian char(200), location_sightings char(200), id char(200)
DuplicateFilter_2
    INPUT_ORDERED_CHOICE = No
    KEYATTR = location
    UNIQUE -> location (writer XLSXW_1)
location (writer XLSXW_1)
    attributes: location auto(20)

Bookmark: Visual Inspection
VISUAL_INSPECTION (reader FILEGDB_1)
    attributes: OBJECTID objectid, SURVEY_NAME text(255), SURVEY_ID_REF text(50), DATE_TIME date, SURVEY_YEAR double, TRANSECT_TARGET_NAME text(255), EASTING double, NORTHING double, PROJ_CRS double, WATER_DEPTH double, HEADING double, SUBSTRATE_TYPE text(50), SUBSTRATE_COMMENT text(255), SEABED_FEATURE text(50), SPONGE_TYPE text(50), SPONGE_DENSITY text(50), LOPHELIA text(50), LOPHELIA_STATUS text(50), OTHER_CORAL_TYPE text(50), OTHER_CORAL_DENSITY text(50), OTHER_FAUNA text(50), OTHER_FAUNA_DENSITY text(50), COMMENT text(255)
    -> CoordinateSystemSetter_10
CoordinateSystemSetter_10
    COORDSYS = EPSG:4326
    -> AttributeManager_4
VISUAL_INSPECTION_BARSEA (reader FILEGDB_1)
    attributes: OBJECTID objectid, SURVEY_NAME text(255), SURVEY_ID_REF text(50), DATE_TIME date, SURVEY_YEAR double, TRANSECT_TARGET_NAME text(255), EASTING double, NORTHING double, PROJ_CRS double, WATER_DEPTH double, HEADING double, SUBSTRATE_TYPE text(50), SUBSTRATE_COMMENT text(255), SEABED_FEATURE text(50), SPONGE_TYPE text(50), SPONGE_DENSITY text(50), LOPHELIA text(50), LOPHELIA_STATUS text(50), OTHER_CORAL_TYPE text(50), OTHER_CORAL_DENSITY text(50), OTHER_FAUNA text(50), OTHER_FAUNA_DENSITY text(50), COMMENT text(255)
    -> CoordinateSystemSetter_2
CoordinateSystemSetter_2
    COORDSYS = EPSG:4326
    -> AttributeManager_4
AttributeManager_4
    ATTR_TABLE:
      RENAME_SET_VALUE OBJECTID > objectid
      RENAME_SET_VALUE SURVEY_NAME > location = @Substring(@Value(location),0,200)
      REMOVE SURVEY_ID_REF
      RENAME_SET_VALUE DATE_TIME > datetime
      RENAME_SET_VALUE SURVEY_YEAR > year
      REMOVE TRANSECT_TARGET_NAME
      REMOVE EASTING
      REMOVE NORTHING
      REMOVE PROJ_CRS
      RENAME_SET_VALUE WATER_DEPTH > sea_depth
      RENAME_SET_VALUE HEADING > heading
      RENAME_SET_VALUE SUBSTRATE_TYPE > substrate = @Substring(@Value(substrate),0,200)
      RENAME_SET_VALUE SUBSTRATE_COMMENT > substrate_status = @Substring(@Value(substrate_status),0,200)
      RENAME_SET_VALUE SEABED_FEATURE > seabed_feature = @Substring(@Value(seabed_feature),0,200)
      RENAME_SET_VALUE SPONGE_TYPE > sponge = @Substring(@Value(sponge),0,200)
      RENAME_SET_VALUE SPONGE_DENSITY > sponge_status = @Substring(@Value(sponge_status),0,200)
      RENAME_SET_VALUE LOPHELIA > lophelia = @Substring(@Value(lophelia),0,200)
      RENAME_SET_VALUE LOPHELIA_STATUS > lophelia_status = @Substring(@Value(lophelia_status),0,200)
      RENAME_SET_VALUE OTHER_CORAL_TYPE > coral = @Substring(@Value(coral),0,200)
      RENAME_SET_VALUE OTHER_CORAL_DENSITY > coral_status = @Substring(@Value(coral_status),0,200)
      RENAME_SET_VALUE OTHER_FAUNA > fauna = @Substring(@Value(fauna),0,200)
      RENAME_SET_VALUE OTHER_FAUNA_DENSITY > fauna_status = @Substring(@Value(fauna_status),0,200)
      RENAME_SET_VALUE COMMENT > comment = @Substring(@Value(comment),0,500)
    -> StringSearcher
StringSearcher
    CASE = no
    MATCHES_ATTR = _match_list
    REGEXP = (\w+\s*\(\w+\s*\w*\))
    STRING_TO_SEARCH = @Value(comment)
    MATCHED -> ListElementCounter
    NOT_MATCHED -> AttributeCreator
ListElementCounter
    CNT_ATTR = diversity
    LIST_NAME = _match_list{}
    -> tbl_visual_inspections (writer POSTGIS_1)
    -> tbl_visual_inspections (writer GEODATABASE_FILE_1)
    -> StatisticsCalculator
AttributeCreator
    ATTR_TABLE = SET_TO diversity = 0
    -> tbl_visual_inspections (writer POSTGIS_1)
    -> tbl_visual_inspections (writer GEODATABASE_FILE_1)
    -> StatisticsCalculator
tbl_visual_inspections (writer GEODATABASE_FILE_1)
    attributes: id integer, location char(200), datetime date, year integer, sea_depth float, heading float, substrate char(200), substrate_status char(200), seabed_feature char(200), sponge char(200), sponge_status char(200), lophelia char(200), lophelia_status char(200), coral char(200), coral_status char(200), fauna char(200), fauna_status char(200), comment char(500), diversity integer
tbl_visual_inspections (writer POSTGIS_1)
    attributes: objectid varchar(200), location varchar(200), datetime date, year int4, sea_depth float8, heading float8, substrate varchar(200), substrate_status varchar(200), seabed_feature varchar(200), sponge varchar(200), sponge_status varchar(200), lophelia varchar(200), lophelia_status varchar(200), coral varchar(200), coral_status varchar(200), fauna varchar(200), fauna_status varchar(200), comment varchar(600), diversity int2
StatisticsCalculator
    COMPUTE_HISTOGRAM = NO
    GROUP_BY = location
    MEAN_ATTR = diversity2
    PREPEND_ATTR_NAME_CHOICE = For multiple results only
    STATS_ATTRS = diversity
    COMPLETE -> BoundingBoxAccumulator
BoundingBoxAccumulator
    ACCUM_ATTRS_NAME = Drop Incoming Attributes
    GROUP_BY = location diversity2
    TOPFER_INDEX = No
    BOUNDING_BOX -> tbl_visual_inspections_locations (writer GEODATABASE_FILE_1)
    BOUNDING_BOX -> tbl_visual_inspections_locations (writer POSTGIS_1)
tbl_visual_inspections_locations (writer POSTGIS_1)
    attributes: location varchar(200), diversity int2
tbl_visual_inspections_locations (writer GEODATABASE_FILE_1)
    attributes: location char(200), diversity char(200)

Bookmark: Photolocations
Creator_2
    GEOMTYPE = Geometry Object
    NUM = 1
    CREATED -> GetFilesInDirectory
GetFilesInDirectory
    dir = W:\Miljødirektoratet\Petroleumsvirksomhet\2017_12_08_marint_kartleggingsprosjekt_nordsjoen\Photos
    file -> StringCaseChanger_4
    directory -> StringCaseChanger_4
StringCaseChanger_4
    ATTRCHOICE = Selected Attributes
    ATTRLIST = path_filename
    CHANGE_TYPE = lowercase
    -> FeatureMerger [SUPPLIER]
PHOTO_LOCATIONS (reader FILEGDB_1)
    attributes: OBJECTID objectid, SURVEY_NAME text(255), SURVEY_ID_REF text(50), PHOTO_DATE date, YEAR double, TRANSECT_TARGET_NAME text(50), EASTING double, NORTHING double, PROJ_CRS double, WATER_DEPTH double, HEADING double, FILE_NAME text(255), QUALITY text(255), REMARKS text(255)
    -> CoordinateSystemSetter_4
CoordinateSystemSetter_4
    COORDSYS = EPSG:4326
    -> StringCaseChanger_3
StringCaseChanger_3
    ATTRCHOICE = Selected Attributes
    ATTRLIST = FILE_NAME
    CHANGE_TYPE = lowercase
    -> FeatureMerger [REQUESTOR]
FeatureMerger
    ATTR_ACCUM_MODE = Merge Supplier
    ATTR_CONFLICT_RES = Use Requestor
    IGNORE_NULLS = No
    JOIN_KEYS = @Value(FILE_NAME) @Value(path_filename) AUTO
    MERGE_TYPE = Attributes Only
    PROCESS_DUPS = NO
    REJECT_NULL_MISSING_KEYS = No
    SUPPLIERS_FIRST = No
    MERGED -> FeatureMerger_2 [SUPPLIER]
    UNMERGED_REQUESTOR -> AttributeManager_2
    UNUSED_SUPPLIER -> tbl_img_without_photolocations (writer GEODATABASE_FILE_2)
    UNUSED_SUPPLIER -> tbl_img_without_photolocations (writer POSTGIS_1)
    <REJECTED> -> FeatureMerger_2 [REQUESTOR]
AttributeManager_2
    ATTR_TABLE:
      RENAME_SET_VALUE OBJECTID > id
      RENAME_SET_VALUE SURVEY_NAME > location
      REMOVE SURVEY_ID_REF
      RENAME_SET_VALUE PHOTO_DATE > datetime
      RENAME_SET_VALUE YEAR > year
      REMOVE TRANSECT_TARGET_NAME
      REMOVE EASTING
      REMOVE NORTHING
      REMOVE PROJ_CRS
      RENAME_SET_VALUE WATER_DEPTH > sea_depth
      RENAME_SET_VALUE HEADING > heading
      RENAME_SET_VALUE FILE_NAME > filename
      RENAME_SET_VALUE QUALITY > quality
      RENAME_SET_VALUE REMARKS > comment
    -> tbl_photolocations_without_img (writer GEODATABASE_FILE_2)
    -> tbl_photolocations_without_img (writer POSTGIS_1)
tbl_photolocations_without_img (writer GEODATABASE_FILE_2)
    attributes: id smallint, location char(200), datetime char(200), year char(200), sea_depth char(200), heading char(200), filename char(200), quality char(200), comment char(200), path_windows char(400)
tbl_photolocations_without_img (writer POSTGIS_1)
    attributes: id varchar(200), location varchar(200), datetime date, year int4, sea_depth float8, heading float8, filename varchar(200), quality varchar(200), comment varchar(600)
FeatureMerger_2
    ATTR_ACCUM_MODE = Merge Supplier
    ATTR_CONFLICT_RES = Use Requestor
    IGNORE_NULLS = No
    JOIN_KEYS = @Value(path_filename) @Value(path_filename) AUTO
    MERGE_TYPE = Attributes and Geometry
    PROCESS_DUPS = NO
    REJECT_NULL_MISSING_KEYS = No
    SUPPLIERS_FIRST = No
    MERGED -> AttributeManager
    UNUSED_SUPPLIER -> AttributeManager
    <REJECTED> -> AttributeManager
AttributeManager
    ATTR_TABLE:
      RENAME_SET_VALUE OBJECTID > id
      RENAME_SET_VALUE SURVEY_NAME > location
      REMOVE SURVEY_ID_REF
      RENAME_SET_VALUE PHOTO_DATE > datetime
      RENAME_SET_VALUE YEAR > year
      REMOVE TRANSECT_TARGET_NAME
      REMOVE EASTING
      REMOVE NORTHING
      REMOVE PROJ_CRS
      RENAME_SET_VALUE WATER_DEPTH > sea_depth
      RENAME_SET_VALUE HEADING > heading
      RENAME_SET_VALUE FILE_NAME > filename
      RENAME_SET_VALUE QUALITY > quality
      RENAME_SET_VALUE REMARKS > comment
      REMOVE path_unix
      REMOVE path_rootname
      REMOVE path_filename
      REMOVE path_extension
      REMOVE path_filesize
      REMOVE path_ownername
      REMOVE path_readonly
      REMOVE path_modified_date
      REMOVE path_created_date
      REMOVE path_accessed_date
      REMOVE path_directory_unix
      REMOVE path_directory_windows
      REMOVE path_type
      REMOVE fme_geometry{0}
      REMOVE fme_rejection_code
      REMOVE fme_geometry{}
    -> StringReplacer_2
StringReplacer_2
    CASE = NO
    FIND_TEXT = W:\Miljødirektoratet\Petroleumsvirksomhet\2017_12_08_marint_kartleggingsprosjekt_nordsjoen\
    NO_MATCH = _FME_NO_OP_
    REGEXP = NO
    SRC_ATTRS = path_windows
    -> tbl_photolocations_with_img (writer GEODATABASE_FILE_2)
    -> tbl_photolocations_with_img (writer POSTGIS_1)
tbl_photolocations_with_img (writer GEODATABASE_FILE_2)
    attributes: id smallint, location char(200), datetime char(200), year char(200), sea_depth char(200), heading char(200), filename char(200), quality char(200), comment char(200), path_windows char(400)
tbl_photolocations_with_img (writer POSTGIS_1)
    attributes: id varchar(200), location varchar(200), datetime date, year int4, sea_depth float8, heading float8, filename varchar(200), quality varchar(200), comment varchar(600), path_windows varchar(200)
tbl_img_without_photolocations (writer GEODATABASE_FILE_2)
    attributes: path_windows char(200), path_rootname char(200), path_filename char(200), path_extension char(200), path_filesize char(200), path_ownername char(200), path_readonly char(200), path_modified_date char(200), path_created_date char(200), path_accessed_date char(200), path_directory_windows char(200), path_type char(200)
tbl_img_without_photolocations (writer POSTGIS_1)
    attributes: path_unix varchar(200), path_windows varchar(200), path_rootname varchar(200), path_filename varchar(200), path_extension varchar(20), path_filesize float8, path_ownername varchar(200), path_readonly varchar(20), path_modified_date date, path_created_date date, path_accessed_date date, path_directory_unix varchar(200), path_directory_windows varchar(200), path_type varchar(20)

Bookmark: SurveyInfo
SURVEY_INFO (reader FILEGDB_1)
    attributes: OBJECTID objectid, SURVEY_NAME text(255), SURVEY_AREA text(50), SURVEY_ID_REF text(50), SURVEY_TYPE text(50), LICENSE text(50), OPERATOR text(50), YEAR double, REPORT_DATE date, EASTING double, NORTHING double, PROJ_CRS double, WATER_DEPTH double, SURVEY_CONTRACTOR text(255), REPORTING_CONTRACTOR text(255), SURVEY_LENGTH double, NUMB_STILLPHOTO double, ROV_TYPE text(255), VESSEL_NAME text(255), REPORT_NAME text(255), VIDEO_NAME text(255), REMARKS text(255)
    -> AttributeManager_7
AttributeManager_7
    ATTR_TABLE:
      RENAME_SET_VALUE OBJECTID > objectid
      RENAME_SET_VALUE SURVEY_NAME > survey_name
      RENAME_SET_VALUE SURVEY_AREA > location
      RENAME_SET_VALUE SURVEY_ID_REF > survey_if_ref
      RENAME_SET_VALUE SURVEY_TYPE > survey_type
      RENAME_SET_VALUE LICENSE > license
      RENAME_SET_VALUE OPERATOR > operator
      RENAME_SET_VALUE YEAR > year
      RENAME_SET_VALUE REPORT_DATE > datetime
      RENAME_SET_VALUE EASTING > x
      RENAME_SET_VALUE NORTHING > y
      SET_TO PROJ_CRS = EPSG:@Value(PROJ_CRS)
      RENAME_SET_VALUE WATER_DEPTH > sea_depth
      RENAME_SET_VALUE SURVEY_CONTRACTOR > survey_contractor
      RENAME_SET_VALUE REPORTING_CONTRACTOR > reporting_contractor
      RENAME_SET_VALUE SURVEY_LENGTH > survey_length
      RENAME_SET_VALUE NUMB_STILLPHOTO > number_of_photos
      RENAME_SET_VALUE ROV_TYPE > rov_type
      RENAME_SET_VALUE VESSEL_NAME > vessel
      RENAME_SET_VALUE REPORT_NAME > report
      RENAME_SET_VALUE VIDEO_NAME > video
      RENAME_SET_VALUE REMARKS > comment
      SET_TO year = FME_CONDITIONAL:DEFAULT_VALUE'@Value(year)'BOOL_OP;OR;COMPOSITE_TEST;<Unused>;TEST datetime ATTRIBUTE_HAS_A_VALUE _FME_BLANK_STRING_'@Substring(@Value(datetime),0,4)'FME_NUM_CONDITIONS2___
    -> FeatureMerger_4 [REQUESTOR]
Creator
    GEOMTYPE = Geometry Object
    NUM = 1
    CREATED -> FeatureReader [INITIATOR]
    CREATED -> FeatureReader_2 [INITIATOR]
FeatureReader
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Only Use Result
    COMBINE_GEOM = Use Result
    DATASET = W:\Miljødirektoratet\Petroleumsvirksomhet\Leveranser\Videos
    FEATURETYPES = PATH
    FORMAT = PATH
    OUTPUT_FEATURES_DISPLAY = Schema and Data Features
    PATH_GLOB_PATTERN = *
    PATH_RECURSE_DIRECTORIES = NO
    PATH_RETRIEVE_FILE_PROPERTIES = NO
    PATH_TYPE = ANY
    PATH -> PythonCaller_2
PythonCaller_2
    NEW_ATTRIBUTES = location
    PYTHONSOURCE:
      import fme
      import fmeobjects
      import re

      def replacer(string, replacement_dict):
          for k, v in replacement_dict.items():
              string = string.replace(k, v)
          return string

      class FeatureProcessor(object):
          def __init__(self):
              self.match_table = {'alkes': 'Alke Sor',
              'alken': 'Alke Nor',
              'byrkje central': 'Byrkje C',
              'byrkje west': 'Byrkje W',
              'børselv': 'Borselv',
              'snøhvitg':'Snohvit',
              'snøhvit f comb':'Snohvit',
              'snøhvit':'Snohvit',
              'norvarg ii':'Nordvarg',
              'kvalross pl':'Kvalross',
              'kramsnø':'Kramsno',
              'goliat eye1&':'Goliat',
              'gloppen ii':'Gloppen',
              'gloppen i':'Gloppen',
              'conocob pl605 south':'Pl605',
              'conocoa pl605 north':'Pl605',
              'askeladd beta':'Askeladd'}
          def input(self,feature):
              vid = feature.getAttribute('path_filename').split('.')[0].lower()
              n_pat = re.compile('\d*\-\d*')
              vid = re.sub(n_pat, '', vid)
              vid = replacer(vid, self.match_table)
              feature.setAttribute('location', vid.strip())
              feature.setAttribute('video', feature.getAttribute('path_filename'))
              self.pyoutput(feature)
          def close(self):
              pass
    PYTHONSYMBOL = FeatureProcessor
    -> StringCaseChanger
StringCaseChanger
    ATTRCHOICE = Selected Attributes
    ATTRLIST = location
    CHANGE_TYPE = Full Title Case
    -> FeatureJoiner [RIGHT]
FeatureReader_2
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Only Use Result
    COMBINE_GEOM = Use Result
    DATASET = W:\Miljødirektoratet\Petroleumsvirksomhet\Leveranser\Reports
    FORMAT = PATH
    OUTPUT_FEATURES_DISPLAY = Schema and Data Features
    PATH_GLOB_PATTERN = *
    PATH_RECURSE_DIRECTORIES = NO
    PATH_RETRIEVE_FILE_PROPERTIES = NO
    PATH_TYPE = ANY
    PATH -> PythonCaller_5
PythonCaller_5
    NEW_ATTRIBUTES = report
    PYTHONSOURCE:
      import fme
      import fmeobjects


      class FeatureProcessor(object):
          def __init__(self):
              pass
          def input(self,feature):


              report = feature.getAttribute('path_filename')
              if len(report) > 1:
                  # save file extension
                  ending = report.split('.')[-1]

                  # join string without file extension
                  report = ''.join(report.split('.')[0:-1])

                  # Remove anything that is not alphanumeric
                  # join with underscore
                  report = ''.join(e for e in report if (e.isalnum() or e == '-' or e == ' '))
                  # replace - with _
                  report = report.replace('-', '_')
                  # replace whitespace with _
                  report = report.replace(' ', '_')
                  # format like: reportname.ending
                  feature.setAttribute('report', '{}.{}'.format(report, ending))

              self.pyoutput(feature)
          def close(self):
              pass
    PYTHONSYMBOL = FeatureProcessor
    -> ListBuilder
ListBuilder
    GROUPS_ORDERED = No
    LIST_ATTRS_TO_INCLUDE = path_windows report path_filename
    LIST_NAME = _list
    -> FeatureMerger_4 [SUPPLIER]
FeatureMerger_4
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> PythonCaller_4
PythonCaller_4
    NEW_ATTRIBUTES = best_match
    PYTHONSOURCE:
      import fme
      import fmeobjects
      from difflib import SequenceMatcher

      class FeatureProcessor(object):
          def __init__(self):
              pass
          def input(self,feature):

              report = feature.getAttribute('report')
              reportList = feature.getAttribute('_list{}.report')
              filepathList = feature.getAttribute('_list{}.path_filename')
              if len(report) > 1:
                  # save file extension
                  ending = report.split('.')[-1]

                  # join string without file extension
                  report = ''.join(report.split('.')[0:-1])

                  # Remove anything that is not alphanumeric
                  # join with underscore
                  report = ''.join(e for e in report if (e.isalnum() or e == '-' or e == ' '))
                  # replace - with _
                  report = report.replace('-', '_')
                  # replace whitespace with _
                  report = report.replace(' ', '_')
                  # format like: reportname.ending
                  ratioList = []
                  for reportName in reportList:
                      ratioList.append(SequenceMatcher(None, report, reportName).ratio())
                  best_match = max(ratioList)
                  best_match_index = ratioList.index(best_match)

                  feature.setAttribute('new_report_name', '{}.{}'.format(report, ending))
                  feature.setAttribute('report', filepathList[best_match_index])
              self.pyoutput(feature)
          def close(self):
              pass
    PYTHONSYMBOL = FeatureProcessor
    -> AttributeRemover
AttributeRemover
    LIST_ATTRS = _list{}.path_windows _list{}.report
    -> CoordinateSystemSetter_3
    -> DuplicateFilter
CoordinateSystemSetter_3
    COORDSYS = EPSG:4326
    -> StringCaseChanger_2
StringCaseChanger_2
    ATTRCHOICE = Selected Attributes
    ATTRLIST = location
    CHANGE_TYPE = Full Title Case
    -> FeatureJoiner [LEFT]
FeatureJoiner
    ATTR_CONFLICT_RES = Use Right
    GEOMETRY_HANDLING = Use Left
    JOIN_KEYS = survey_name location STRING
    JOIN_MODE = Inner
    JOINED -> tbl_survey_info (writer POSTGIS_1)
    JOINED -> tbl_survey_info (writer GEODATABASE_FILE_1)
    UNJOINED_LEFT -> FeatureJoiner_2 [LEFT]
    UNJOINED_RIGHT -> FeatureJoiner_2 [RIGHT]
FeatureJoiner_2
    ATTR_CONFLICT_RES = Use Left
    GEOMETRY_HANDLING = Use Left
    JOIN_KEYS = location location STRING
    JOIN_MODE = Inner
    JOINED -> tbl_survey_info (writer POSTGIS_1)
    JOINED -> tbl_survey_info (writer GEODATABASE_FILE_1)
    UNJOINED_LEFT -> tbl_survey_info (writer POSTGIS_1)
    UNJOINED_LEFT -> tbl_survey_info (writer GEODATABASE_FILE_1)
    UNJOINED_RIGHT -> tbl_video_unmatched_location (writer POSTGIS_1)
    UNJOINED_RIGHT -> tbl_video_unjoined (writer GEODATABASE_FILE_1)
tbl_survey_info (writer GEODATABASE_FILE_1)
    attributes: objectid char(200), survey_name char(200), location char(200), survey_if_ref char(200), survey_type char(200), license char(200), operator char(200), datetime date, sea_depth double, survey_contractor char(200), reporting_contractor char(200), survey_length char(200), number_of_photos char(200), rov_type char(200), vessel char(200), report char(200), video char(200), comment char(200), year integer, path_windows char(200), path_rootname char(200), path_filename char(200), path_extension char(200)
tbl_survey_info (writer POSTGIS_1)
    attributes: objectid varchar(200), survey_name varchar(200), location varchar(200), survey_if_ref varchar(200), survey_type varchar(200), license varchar(200), operator varchar(200), datetime date, sea_depth float8, survey_contractor varchar(200), reporting_contractor varchar(200), survey_length varchar(200), number_of_photos int4, rov_type varchar(200), vessel varchar(200), report varchar(200), video varchar(200), comment varchar(200), year varchar(200), path_windows varchar(200), path_rootname varchar(200), path_filename varchar(200), path_extension varchar(20), path_filesize float8
tbl_video_unjoined (writer GEODATABASE_FILE_1)
    attributes: path_unix char(200), path_windows char(200), path_rootname char(200), path_filename char(200), path_extension char(200), path_filesize char(200), path_ownername char(200), path_readonly char(200), path_modified_date char(200), path_created_date char(200), path_accessed_date char(200), path_directory_unix char(200), path_directory_windows char(200), path_type char(200), location char(200)
tbl_video_unmatched_location (writer POSTGIS_1)
    attributes: path_unix varchar(200), path_windows varchar(200), path_rootname varchar(200), path_filename varchar(200), path_extension varchar(20), path_filesize float8, path_ownername varchar(200), path_readonly varchar(200), path_modified_date varchar(200), path_created_date varchar(200), path_accessed_date varchar(200), path_directory_unix varchar(200), path_directory_windows varchar(200), path_type varchar(200), fme_geometry{0} varchar(200), location varchar(200)
DuplicateFilter
    INPUT_ORDERED_CHOICE = No
    KEYATTR = report
    UNIQUE -> DuplicateFilter_Unique
DuplicateFilter_Unique: Inspector [off]

FME custom transformer GetFilesInDirectory

Parameters:
- dir = W:\Miljødirektoratet\Petroleumsvirksomhet\2017_12_08_marint_kartleggingsprosjekt_nordsjoen\Photos   # Folder

input (input)
    -> FeatureReader [INITIATOR]
FeatureReader
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Only Use Result
    CACHE_TIMEOUT_HRS = 240
    COMBINE_GEOM = Use Result
    DATASET = $(dir)
    FORMAT = PATH
    OUTPUT_FEATURES_DISPLAY = Schema and Data Features
    PATH_GLOB_PATTERN = *
    PATH_RECURSE_DIRECTORIES = NO
    PATH_RETRIEVE_FILE_PROPERTIES = NO
    PATH_TYPE = ANY
    PATH -> Tester
Tester
    BOOL_OP = OR
    TEST_CLAUSE = TEST @Value(path_type) = directory
    PASSED -> FeatureReader_2 [INITIATOR]
    FAILED -> StringCaseChanger
FeatureReader_2
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Only Use Result
    CACHE_TIMEOUT_HRS = 240
    COMBINE_GEOM = Use Result
    DATASET = @Value(path_windows)
    FORMAT = PATH
    OUTPUT_FEATURES_DISPLAY = Schema and Data Features
    PATH_GLOB_PATTERN = *
    PATH_RECURSE_DIRECTORIES = NO
    PATH_RETRIEVE_FILE_PROPERTIES = NO
    PATH_TYPE = ANY
    PATH -> Tester_2
Tester_2
    BOOL_OP = OR
    TEST_CLAUSE = TEST @Value(path_type) = directory
    PASSED -> FeatureReader_3 [INITIATOR]
    FAILED -> StringCaseChanger
FeatureReader_3
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Only Use Result
    CACHE_TIMEOUT_HRS = 240
    COMBINE_GEOM = Use Result
    DATASET = @Value(path_windows)
    FORMAT = PATH
    OUTPUT_FEATURES_DISPLAY = Schema and Data Features
    PATH_GLOB_PATTERN = *
    PATH_RECURSE_DIRECTORIES = NO
    PATH_RETRIEVE_FILE_PROPERTIES = NO
    PATH_TYPE = ANY
    PATH -> Tester_3
Tester_3
    BOOL_OP = OR
    TEST_CLAUSE = TEST @Value(path_type) = directory
    PASSED -> FeatureReader_4 [INITIATOR]
    FAILED -> StringCaseChanger
FeatureReader_4
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Only Use Result
    CACHE_TIMEOUT_HRS = 240
    COMBINE_GEOM = Use Result
    DATASET = @Value(path_windows)
    FORMAT = PATH
    OUTPUT_FEATURES_DISPLAY = Schema and Data Features
    PATH_GLOB_PATTERN = *
    PATH_RECURSE_DIRECTORIES = NO
    PATH_RETRIEVE_FILE_PROPERTIES = NO
    PATH_TYPE = ANY
    PATH -> Tester_4
Tester_4
    BOOL_OP = OR
    TEST_CLAUSE = TEST @Value(path_type) = directory
    PASSED -> FeatureReader_5 [INITIATOR]
    FAILED -> StringCaseChanger
FeatureReader_5
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Only Use Result
    CACHE_TIMEOUT_HRS = 240
    COMBINE_GEOM = Use Result
    DATASET = @Value(path_windows)
    FORMAT = PATH
    OUTPUT_FEATURES_DISPLAY = Schema and Data Features
    PATH_GLOB_PATTERN = *
    PATH_RECURSE_DIRECTORIES = NO
    PATH_RETRIEVE_FILE_PROPERTIES = NO
    PATH_TYPE = ANY
    PATH -> Tester_5
Tester_5
    BOOL_OP = OR
    TEST_CLAUSE = TEST @Value(path_type) = directory
    PASSED -> StringCaseChanger
    FAILED -> StringCaseChanger
StringCaseChanger
    ATTRCHOICE = Selected Attributes
    ATTRLIST = path_extension
    CHANGE_TYPE = UPPERCASE
    -> AttributeFilter
AttributeFilter
    ATTR_NAME = path_type
    ATTR_VALUES = file,directory,<Empty>,<Missing>,<Null>,<Unfiltered>
    file -> file (output)
    directory -> directory (output)
    <EMPTY> -> directory (output)
    <MISSING> -> directory (output)
    <NULL> -> directory (output)
    <UNFILTERED> -> directory (output)
file (output)
directory (output)
